module traffic-app-data-types {
  namespace "https://github.com/SpirentOrion/gemini/model/test/traffic-app-data-types";
  prefix ttte;

  organization
    "Spirent";
  contact
    "Spirent";
  description
    "This module defines topology data types required for traffic-app .";

 revision 2021-01-06 {
    description
      "Changed range for hex-number-8-bit.";
    reference
      "0.0.2";
  }

  revision 2020-11-19 {
    description
      "Initial revision.";
    reference
      "0.0.1";
  }

  typedef prefix32 {
    type int32 {
      range "1..32";
    }
    description
      "IPv4 Prefix range";
  }

  typedef prefix128 {
    type int32 {
      range "1..128";
    }
    description
      "IPv6 Prefix range";
  }

  typedef hex-number-8-bit {
    type string {
      length "3..4";
      pattern '0[xX][0-9a-fA-F]+';
    }
    description
      "Hexa decimal number data type.";
  }

  typedef vlan-id-type {
    type int16 {
      range "0..4094";
    }
    description
      "Vlan id";
  }

  typedef tpid-type {
    type string {
      pattern '0X8100|0x88A8|0X9100|0X9200|0X9300';
    }
    description
      "Tag Protocol Identifier. The values can be any the values mentioned in the pattern.";
  }

  typedef priority-type {
    type int32 {
      range "1..7";
    }
    description
      "Priority. The values can be from 1 to 7.";
  }



}
